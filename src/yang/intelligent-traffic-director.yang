module intelligent-traffic-director {

  namespace "http://com/example/intelligenttrafficdirector";
  prefix itd;

  import ietf-inet-types { prefix inet; }
  import tailf-ncs { prefix ncs; }
  import tailf-common { prefix tailf; }
  import ftdv-ngfw { prefix ftdv; }

  typedef side {
    type enumeration {
      enum "inside";
      enum "outside";
    }
  }

  grouping device-grouping {
    list devices {
      key device;
      leaf device {
        type leafref {
          path "/ncs:devices/ncs:device/ncs:name";
        }
      }
      leaf side {
        type side;
      }
    }
  }

  grouping service-grouping {
    leaf ingress-interface {
      type string;
    }
    leaf virtual-ip {
      type inet:ipv4-address;
    }
    leaf virtual-ip-mask {
       type string;
    }
    leaf-list node-ip {
      type inet:ipv4-address;
    }
    leaf buckets {
      type uint16 {
          range 2..256;
      }
    }
    leaf method {
      type enumeration {
        enum "src";
        enum "dst";
      }
    }
  }

  list intelligent_traffic_director {
    key service-name;

    uses ncs:service-data;
    ncs:servicepoint "intelligent-traffic-director";

    leaf service-name {
      type string;
    }
    uses device-grouping;
    list sides {
      key side;
      leaf side {
        type side;
      }
      leaf-list devices {
        type leafref {
          path "../../devices/device";
        }
      }
      uses service-grouping;
    }
  }

  augment /ftdv:vnf-manager/ftdv:site {
    container intelligent-traffic-director {
      uses device-grouping;
    }
  }

  augment /ftdv:vnf-manager/ftdv:site/ftdv:networks/ftdv:network {
    leaf intelligent-traffic-director-side {
      type side;
    }
  }

  augment /ftdv:vnf-manager/ftdv:site/ftdv:vnf-deployment/ftdv:device {
    container load-balanced {
      presence "true";
    }
    tailf:action load-balance {
      tailf:actionpoint add-load-balanced-device;
      input {
        leaf enable {
          type boolean;
        }
      }
      output {}
    }
  }
  augment /ftdv:vnf-manager/ftdv:site/ftdv:vnf-deployment/ftdv:scaling/ftdv:load-balance/ftdv:load-balancer {
    container cisco-intelligent-traffic-director {
      tailf:action initialize {
        tailf:actionpoint initialize-itd-action;
        input {}
        output {
          leaf result {
            type string;
          }
        }
      }
      tailf:action deploy {
        tailf:actionpoint configure-itd-action;
        input {}
        output {
          leaf result {
            type string;
          }
        }
      }
      list sides {
        key side;
        leaf side {
          type side;
        }
        leaf site-network {
          type leafref {
            path "../../../../../ftdv:networks/ftdv:network/ftdv:name";
          }
        }
        uses service-grouping;
      }
    }
  }
}
